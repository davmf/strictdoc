package 'Diagram requirements' {
    doc /*
     * Requirements text below the diagram.
     */

    requirement <'DGM-REQ-1'> 'Heating' {
        doc /*
         * The station shall heat the sample.
         */
    }
}
