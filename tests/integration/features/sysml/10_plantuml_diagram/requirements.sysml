package 'PlantUML requirements' {
    doc /*
     * Requirements text below the diagram, with a </script> tag.
     */

    requirement <'PUML-REQ-1'> 'Heating' {
        doc /*
         * The station shall heat the sample.
         */
    }
}
