package 'Image requirements' {
    requirement <'IMG-REQ-1'> 'Requirement with an image' {
        doc /*
         * The display shall look like this:
         *
         * .. image:: ./_assets/diagram.svg
         */
    }
}
