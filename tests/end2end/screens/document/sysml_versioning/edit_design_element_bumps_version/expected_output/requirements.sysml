package 'Requirements' {
    requirement <'SYS-1'> 'Throughput' {
        @StrictDocVersioning::ItemVersion { version = 4; contentHash = "c09db72d9057f3bc"; }
        doc /*
         * The instrument shall complete 96 samples per shift.
         */
    }
}
