package DoorRequirements {
    doc /*
     * Requirements of the door.
     */

    requirement <'DOOR-REQ-1'> 'Open on command' {
        doc /*
         * The door shall open when it receives the open command.
         */
    }
}
