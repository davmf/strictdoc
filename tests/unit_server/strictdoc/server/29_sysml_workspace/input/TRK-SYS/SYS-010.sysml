package 'SYS-010' {
    private import ScalarValues::*;
    private import 'TRK-STK'::*;

    requirement <'SYS-010'> 'Dry boil' {
        doc /*
         * The kettle shall switch off within 5 s when it is empty.
         */
    }
}
