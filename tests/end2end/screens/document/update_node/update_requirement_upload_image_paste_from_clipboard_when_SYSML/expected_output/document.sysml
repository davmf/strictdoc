package 'Document 1' {
    requirement <'REQ-1'> 'Requirement title' {
        doc /*
         * Requirement statement.
         *
         * .. image:: ./_assets/REQ-1/picture.svg
         */
    }
}
