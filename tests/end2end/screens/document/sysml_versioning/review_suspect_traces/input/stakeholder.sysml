package 'Stakeholder requirements' {
    requirement <'STK-1'> 'Throughput' {
        @StrictDocVersioning::ItemVersion { version = 3; contentHash = "94ff725b56bbd773"; }
        doc /*
         * The lab shall process 96 samples per shift.
         */
    }
}
