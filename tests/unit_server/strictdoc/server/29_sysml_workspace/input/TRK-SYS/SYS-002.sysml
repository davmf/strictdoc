package 'SYS-002' {
    private import ScalarValues::*;
    private import 'TRK-STK'::*;

    requirement <'SYS-002'> 'Keep warm' {
        doc /*
         * The kettle shall keep the water above 80 C for 30 min.
         */
    }
}
